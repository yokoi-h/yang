module bgp-multiprotocol {

  yang-version "1";

  // namespace
  namespace "http://openconfig.net/yang/bgp-multiprotocol";

  prefix "bgp-mp";

  // import some basic inet types
  import routing-policy { prefix rpol; }
  import bgp-operational { prefix bgp-op; }

  // meta
  organization
    "OpenConfig working group";

  contact
    "OpenConfig working group
    netopenconfig@googlegroups.com";

  description
    "This module is part of a YANG model for BGP protocol
    configuration, focusing on configuration of multiprotocol
    BGP, in particular various relevant address families (AFI) and
    sub-address families (SAFI).

    Identities (rather than enumerated types) are used to identify
    each AFI / SAFI type to make it easier for users to extend to
    pre-standard or custom AFI/SAFI types.  This module is only
    intended to capture the most";


  revision "2014-11-30" {
    description
      "Refactored multiprotocol module";
    reference "TBD";
  }

  // extension statements

  // feature statements

  // typedef statements
  // TODO: move to common bgp-types module.
  typedef percentage {
    type uint8 {
      range "0..100";
    }
    description
      "Integer indicating a percentage value";
  }

  // identity statements
  identity afi-safi-type {
    description
      "Base identity type for AFI,SAFI tuples for BGP-4";
    reference "RFC4760 - multiprotocol extensions for BGP-4";
  }

  identity ipv4-unicast {
    base afi-safi-type;
    description
      "IPv4 unicast (AFI,SAFI = 1,1)";
    reference "RFC4760";
  }

  identity ipv6-unicast {
    base afi-safi-type;
    description
      "IPv6 unicast (AFI,SAFI = 2,1)";
    reference "RFC4760";
  }

  identity ipv4-multicast {
    base afi-safi-type;
    description
      "IPv4 multicast (AFI,SAFI = 1,2)";
    reference "RFC4760";
  }

  identity ipv6-multicast {
    base afi-safi-type;
    description
      "IPv6 multicast (AFI,SAFI = 2,2)";
    reference "RFC4760";
  }

  identity ipv4-labelled-unicast {
    base afi-safi-type;
    description
      "Labelled IPv4 unicast (AFI,SAFI = 1,4)";
    reference "RFC3107";
  }

  identity ipv6-labelled-unicast {
    base afi-safi-type;
    description
      "Labelled IPv6 unicast (AFI,SAFI = 2,4)";
    reference "RFC3107";
  }

  identity l3vpn-ipv4-unicast {
    base afi-safi-type;
    description
      "Unicast IPv4 MPLS L3VPN (AFI,SAFI = 1,128)";
    reference "RFC4364";
  }

  identity l3vpn-ipv6-unicast {
    base afi-safi-type;
    description
      "Unicast IPv6 MPLS L3VPN (AFI,SAFI = 2,128)";
    reference "RFC4659";
  }

  identity l3vpn-ipv4-multicast {
    base afi-safi-type;
    description
      "Multicast IPv4 MPLS L3VPN (AFI,SAFI = 1,129)";
    reference "RFC6514";
  }

  identity l3vpn-ipv6-multicast {
    base afi-safi-type;
    description
      "Multicast IPv6 MPLS L3VPN (AFI,SAFI = 2,129)";
    reference "RFC6514";
  }

  identity l2vpn-vpls {
    base afi-safi-type;
    description
      "BGP-signalled VPLS (AFI,SAFI = 25,65)";
    reference "RFC4761";
  }

  identity l2vpn-evpn {
    base afi-safi-type;
    description
      "BGP MPLS Based Ethernet VPN (AFI,SAFI = 25,70)";
  }

  // grouping statements

  // common groupings (used by multiple afi-safi groupings)

  grouping all-afi-safi-common {
    description
      "Grouping for configuration common to all AFI,SAFI";

    // import and export policy included for the afi/safi
    uses rpol:apply-policy-group;

    container prefix-limit {
      description
        "Configure the maximum number of prefixes that will be
        accepted from a peer";

      leaf max-prefixes {
        type uint32;
        description
          "Maximum number of prefixes that will be accepted
          from the neighbour";
      }

      leaf shutdown-threshold-pct {
        type percentage;
        description
          "Threshold on number of prefixes that can be received
          from a neighbour before generation of warning messages
          or log entries. Expressed as a percentage of
          max-prefixes";
      }

      leaf restart-timer {
        type decimal64 {
          fraction-digits 2;
        }
        units "seconds";
        description
          "Time interval in seconds after which the BGP session
          is re-established after being torn down due to exceeding
          the max-prefix limit.";
      }
    }
  }

  grouping ipv4-ipv6-unicast-common {
    description
      "Common configuration that is applicable for IPv4 and IPv6
      unicast";

    // include common afi-safi options.
    uses all-afi-safi-common;

    // configuration options that are specific to IPv[46] unicast
    leaf send-default-route {
      type boolean;
      default "false";
      description
        "If set to true, send the default-route to the neighbour(s)";
    }
  }

  grouping ipv4-ipv6-multicast-common {
    description
      "Common configuration that is applicable for IPv4 and IPv6
      multicast";

      // include common afi-safi options
      uses all-afi-safi-common;

      // configuration items that are specific to IPv[46] multicafst
      // placeholder
  }

  grouping l3vpn-ipv4-ipv6-unicast-common {
    description
      "Common configuration applied across L3VPN for IPv4
       and IPv6";

    // placeholder -- specific configuration options that are generic
    // across IPv[46] unicast address families.
    uses all-afi-safi-common;
  }

  grouping l3vpn-ipv4-ipv6-multicast-common {
    description
      "Common configuration applied across L3VPN for IPv4
      and IPv6";

    // placeholder -- specific configuration options that are
    // generic across IPv[46] multicast address families.
    uses all-afi-safi-common;
  }

  grouping l2vpn-common {
    description
      "Common configuration applied across L2VPN address
      families";

    // placeholder -- specific configuration options that are
    // generic across L2VPN address families
    uses all-afi-safi-common;
  }

  // groupings for specific configuration options per AFI,SAFI -
  // included only when the set AFI,SAFI matches the group (enforced
  // by XPATH)

  // TODO: evalute whether presence should indicate whether an
  // AFI,SAFI is enabled, or whether an enabled boolean is required.

  grouping ipv4-unicast-group {
    description
      "Group for IPv4 Unicast configuration options";

    container ipv4-unicast {
      when "../afi-safi-name = 'bgp-mp:ipv4-unicast'" {
        description
          "Include this container for IPv4 Unicast specific
          configuration";
      }

      leaf enabled {
        type boolean;
        default false;
        description
          "This leaf indicates whether the IPv4 Unicast AFI,SAFI is
          enabled for the neighbour or group";
      }

      description "IPv4 unicast configuration options";

      // include common IPv[46] unicast options
      uses ipv4-ipv6-unicast-common;

      // placeholder for IPv4 unicast  specific configuration
    }
  }

  grouping ipv6-unicast-group {
    description
      "Group for IPv6 Unicast configuration options";

    container ipv6-unicast {
      when "../afi-safi-name = 'bgp-mp:ipv6-unicast'" {
        description
          "Include this container for IPv6 Unicast specific
          configuration";
      }

      leaf enabled {
        type boolean;
        default false;
        description
          "This leaf indicates whether the IPv6 Unicast AFI,SAFI is
          enabled for the neighbour or group";
      }

      description "IPv6 unicast configuration options";

      // include common IPv[46] unicast options
      uses ipv4-ipv6-unicast-common;

      // placeholder for IPv6 unicast specific configuration
      // options
    }
  }

  grouping ipv4-multicast-group {
    description
      "Group for IPv4 Multicast configuration options";

    container ipv4-multicast {
      when "../afi-safi-name = 'bgp-mp:ipv4-multicast'" {
        description
          "Include this container for IPv4 Multicast specific
          configuration";
      }

      leaf enabled {
        type boolean;
        default false;
        description
          "This leaf indicates whether the IPv4 Multicast AFI,SAFI
          is enabled for the neighbour or group";
      }

      description "IPv4 unicast configuration options";

      // include common IPv[46] multicast options
      uses ipv4-ipv6-multicast-common;

      // placeholder for IPv4 multicast specific configuration
      // options

    }
  }

  grouping ipv6-multicast-group {
    description
      "Group for IPv6 Multicast configuration options";

    container ipv6-multicast {
      when "../afi-safi-name = 'bgp-mp:ipv6-multicast'" {
        description
          "Include this container for IPv6 Multicast specific
          configuration";
      }

      leaf enabled {
        type boolean;
        default false;
        description
          "This leaf indicates whether the IPv6 Multicast AFI,SAFI
          is enabled for the neighbour or group";
      }

      description "IPv6 multicast configuration options";

      // include common IPv[46] multicast options
      uses ipv4-ipv6-multicast-common;

      // placeholder for IPv4 multicat specific configuration
      // options

    }
  }

  grouping ipv4-labelled-unicast-group {
    description
      "Group for IPv4 Labelled Unicast configuration options";

    container ipv4-labelled-unicast {
      when "../afi-safi-name = 'bgp-mp:ipv4-labelled-unicast'" {
        description
          "Include this container for IPv4 Labelled Unicast specific
          configuration";
      }

      leaf enabled {
        type boolean;
        default false;
        description
          "This leaf indicates whether the IPv4 Labelled Unicast
          AFI,SAFI is enabled for the neighbour or group";
      }

      description "IPv4 Labelled Unicast configuration options";

      uses all-afi-safi-common;

      // placeholder for IPv4 Labelled Unicast specific config
      // options
    }
  }

  grouping ipv6-labelled-unicast-group {
    description
      "Group for IPv6 Labelled Unicast configuration options";

    container ipv6-labelled-unicast {
      when "../afi-safi-name = 'bgp-mp:ipv6-labelled-unicast'" {
        description
          "Include this container for IPv6 Labelled Unicast specific
          configuration";
      }

      leaf enabled {
        type boolean;
        default false;
        description
          "This leaf indicates whether the IPv6 Labelled Unicast
          AFI,SAFI is enabled for the neighbour or group";
      }

      description "IPv6 Labelled Unicast configuration options";

      uses all-afi-safi-common;

      // placeholder for IPv6 Labelled Unicast specific config
      // options.
    }
  }

  grouping l3vpn-ipv4-unicast-group {
    description
      "Group for IPv4 Unicast L3VPN configuration options";

    container l3vpn-ipv4-unicast {
      when "../afi-safi-name = 'bgp-mp:l3vpn-ipv4-unicast'" {
        description
          "Include this container for IPv4 Unicast L3VPN specific
          configuration";
      }

      leaf enabled {
        type boolean;
        default false;
        description
          "This leaf indicates whether the IPv4 Unicast L3VPN
          AFI,SAFI is enabled for the neighbour or group";
      }

      description "Unicast IPv4 L3VPN configuration options";

      // include common L3VPN configuration options
      uses l3vpn-ipv4-ipv6-unicast-common;

      // placeholder for IPv4 Unicast L3VPN specific config options.
    }
  }

  grouping l3vpn-ipv6-unicast-group {
    description
      "Group for IPv6 Unicast L3VPN configuration options";

    container l3vpn-ipv6-unicast {
      when "../afi-safi-name = 'bgp-mp:l3vpn-ipv6-unicast'" {
        description
          "Include this container for unicast IPv6 L3VPN specific
          configuration";
      }

      leaf enabled {
        type boolean;
        default false;
        description
          "This leaf indicates whether the IPv6 Unicast L3VPN
          AFI,SAFI is enabled for the neighbour or group";
      }

      description "Unicast IPv6 L3VPN configuration options";

      // include common L3VPN configuration options
      uses l3vpn-ipv4-ipv6-unicast-common;

      // placeholder for IPv6 Unicast L3VPN specific configuration
      // options
    }
  }

  grouping l3vpn-ipv4-multicast-group {
    description
      "Group for IPv4 L3VPN multicast configuration options";

    container l3vpn-ipv4-multicast {
      when "../afi-safi-name = 'bgp-mp:l3vpn-ipv4-multicast'" {
        description
          "Include this container for multicast IPv6 L3VPN specific
          configuration";
      }

      leaf enabled {
        type boolean;
        default false;
        description
          "This leaf indicates whether the L3VPN IPv4 Multicast
          AFI,SAFI is enabled for the neighbour or group";
      }

      description "Multicast IPv4 L3VPN configuration options";

      // include common L3VPN multicast options
      uses l3vpn-ipv4-ipv6-multicast-common;

      // placeholder for IPv4 Multicast L3VPN specific configuration
      // options
    }
  }

  grouping l3vpn-ipv6-multicast-group {
    description
      "Group for IPv6 L3VPN multicast configuration options";

    container l3vpn-ipv6-multicast {
      when "../afi-safi-name = 'bgp-mp:l3vpn-ipv6-multicast'" {
        description
          "Include this container for multicast IPv6 L3VPN specific
          configuration";
      }

      leaf enabled {
        type boolean;
        default false;
        description
          "This leaf indicates whether the IPv6 Multicast L3VPN
          AFI,SAFI is enabled for the neighbour or group";
      }

      description "Multicast IPv6 L3VPN configuration options";

      // include common L3VPN multicast options
      uses l3vpn-ipv4-ipv6-multicast-common;

      // placeholder for IPv6 Multicast L3VPN specific configuration
      // options
    }
  }

  grouping l2vpn-vpls-group {
    description
      "Group for BGP-signalled VPLS configuration options";

    container l2vpn-vpls {
      when "../afi-safi-name = 'bgp-mp:l2vpn-vpls'" {
        description
          "Include this container for BGP-signalled VPLS specific
          configuration";
      }

      leaf enabled {
        type boolean;
        default false;
        description
          "This leaf indicates whether the BGP-signalled VPLS
          AFI,SAFI is enabled for the neighbour";
      }

      description "BGP-signalled VPLS configuration options";

      // include common L2VPN options
      uses l2vpn-common;

      // placeholder for BGP-signalled VPLS specific configuration
      // options
    }
  }

  grouping l2vpn-evpn-group {
    description
      "Group for BGP EVPN configuration options";

    container l2vpn-evpn {
      when "../afi-safi-name = 'bgp-mp:l2vpn-evpn'" {
        description
          "Include this container for BGP EVPN specific
          configuration";
      }

      presence
        "Presence of this container indicates that the BGP EVPN
        AFI,SAFI is enabled";

      description "BGP EVPN configuration options";

      // include common L2VPN options
      uses l2vpn-common;

      // placeholder for BGP EVPN specific configuration options
    }
  }

  grouping address-family-list {
    description
      "Combines the set of supported AFI-SAFI configuration data";

      uses ipv4-unicast-group;
      uses ipv6-unicast-group;
      uses ipv4-multicast-group;
      uses ipv6-multicast-group;
      uses ipv4-labelled-unicast-group;
      uses ipv6-labelled-unicast-group;
      uses l3vpn-ipv4-unicast-group;
      uses l3vpn-ipv6-unicast-group;
      uses l3vpn-ipv4-multicast-group;
      uses l3vpn-ipv6-multicast-group;
      uses l2vpn-vpls-group;
      uses l2vpn-evpn-group;
  }

  // grouping to be included on a per-AFI,SAFI basis
  grouping address-family-configuration {
    description
      "Configuration for a particular AFI,SAFI";

    list afi-safi {
      key "afi-safi-name";
      description
        "Per-AFI,SAFI configuration - identified by
        AFI,SAFI name.";
      leaf afi-safi-name {
        type identityref {
          base "afi-safi-type";
        }
        description
          "AFI,SAFI";
      }

      uses address-family-list;


    }
  }

  // grouping for configuration options which are applicable
  // to global, peer-groups, and afi-safi

  grouping bgp-global-group-afi-safi-config {
    description
      "Grouping for configuration options that are included
      in the global AFI-SAFI config, per-AFI-SAFI and within
      a peer-group";

    container use-multiple-paths {

      presence
        "Presence of this container indicates that multipath
         is enabled for both eBGP and iBGP, absence indicates
         that multi-path is not used";

      description
        "Configuration of BGP multi-path for iBGP and eBGP";

      container ebgp {
        description
          "Configuration of BGP multipath to enable load sharing
          across multiple paths to eBGP peers";

        leaf allow-multiple-as {
         type boolean;
         default "false";
         description
          "Allow multipath to use paths from different neighbouring
          ASes.  The default is to only consider multiple paths from
          the same neighbouring AS.";
        }

        leaf maximum-paths {
         type uint32;
         default 1;
         description
          "Maximum number of parallel paths to consider when using
          BGP multipath. The default is use a single path.";
        }
      }

      container ibgp {
        description
          "Configuration of BGP multipath to enable load-sharing
          across multiple paths to iBGP peers";

        leaf maximum-paths {
          type uint32;
          default 1;
          description
            "Maximum number of parallel paths to consider when using
            iBGP multipath. The default is to use a single path";
        }
      }
    }
  }

  // groupings for global AFI,SAFI configuration

  grouping global-individual-afi-safi-configuration-group {
    description
      "Configuration parameters which can be specified for
      all AFI,SAFI - as well as on a per-AFI,SAFI basis -
      for all AFI,SAFIs";

    uses bgp-global-group-afi-safi-config;

  }

  grouping global-afi-neutral-configuration-group {
    description
      "Configuration parameters applicable to an entire AFI,SAFI
      across all peers and groups";

    container route-selection-options {
      description
        "Set of configuration options that govern best
         path selection.";
      leaf always-compare-med {
        type boolean;
        default "false";
        description
          "Compare multi-exit discriminator (MED) value from
          different ASes when selecting the best route.  The
          default behavior is to only compare MEDs for paths
          received from the same AS.";
      }

      leaf ignore-as-path-length {
        type boolean;
        default "false";
        description
          "Ignore the AS path length when selecting the best path.
          The default is to use the AS path length and prefer paths
          with shorter length.";
      }

      leaf external-compare-router-id {
        type boolean;
        default "true";
        description
          "When comparing similar routes received from external
          BGP peers, use the router-id as a criterion to select
          the active path.";
      }

      leaf advertise-inactive-routes {
        type boolean;
        default "false";
        description
          "Advertise inactive routes to external peers.  The
          default is to only advertise active routes.";
      }

      leaf enable-aigp {
        type empty;
        description
          "Flag to enable sending / receiving accumulated IGP
          attribute in routing updates";
      }

      leaf ignore-next-hop-igp-metric {
        type boolean;
        default "false";
        description
          "Ignore the IGP metric to the next-hop when calculating
          BGP best-path. The default is to select the route for
          which the metric to the next-hop is lowest";
      }
    }

    uses global-individual-afi-safi-configuration-group;
  }

  // grouping to be included under the global BGP configuration to
  // set per-AFI,SAFI global behaviours (e.g., route selection)
  grouping global-address-family-configuration {
    description
      "Configuration impacting the route selection, or global
      characteristics of a particular AFI,SAFI";

    uses global-individual-afi-safi-configuration-group;

    list global-afi-safi {
      key "afi-safi-name";

      description
        "AFI,SAFI configuration available for the
        neighbour or group";

      leaf afi-safi-name {
        type identityref {
          base "afi-safi-type";
        }
        description "AFI,SAFI";
      }

      uses global-afi-neutral-configuration-group;
      uses address-family-list;

      // if we have AFI,SAFI specific configuration hooks that
      // will be global, they can be included like:
      //uses global-ipv4-unicast-configuration-group;
      //uses global-ipv6-unicast-configuration-group;
    }
  }

  // data definition statements

  // augment statements

  // rpc statements

  // notification statements

}
